;;; PCAP Sensor Layout Generator
;;; Point-for-point rewrite of the complete legacy sensor generator.
;;; Command: PCAPSENSOR
;;; Generates Top/Bottom ITO, Ag fan-out, and laser-isolation layers.

(vl-load-com)

(defun pcap:ensure-layer (name color /)
  (if (not (tblsearch "LAYER" name))
    (entmake
      (list '(0 . "LAYER")
            '(100 . "AcDbSymbolTableRecord")
            '(100 . "AcDbLayerTableRecord")
            (cons 2 name)
            '(70 . 0)
            (cons 62 color)
            '(6 . "CONTINUOUS"))))
  name)

(defun pcap:line (start end /)
  ;; Reject the zero-length LINE entities emitted by the legacy implementation.
  (if (and start end (> (distance start end) 1e-9))
    (entmakex (list '(0 . "LINE") (cons 8 (getvar "CLAYER"))
                    (cons 10 start) (cons 11 end)))))

(defun pcap:getdist-default (message default / value)
  (initget 6)
  (setq value (getdist (strcat message " <" (rtos default 2 3) ">: ")))
  (if value value default))

(defun pcap:getint-default (message default / value)
  (initget 6)
  (setq value (getint (strcat message " <" (itoa default) ">: ")))
  (if value value default))

(defun pcap:fanout-horizontal ( da pcd asw bsw ast en  / nclayer xast yast bst st xst yst xen yen xdd ydd ts xa ya xb yb xc yc aa bb cc row col)
(vl-load-com)
(setvar "OsnapCoord" 1)
  (setq xast (car ast)
        yast (cadr ast))
  (setq bst (list xast (+ yast bsw)))
  (setq st (list xast (- yast asw)))
  (setq xst (car st)
        yst (cadr st))
  (setq xen (car en)
        yen (cadr en))
  (setq nclayer (getvar "CLAYER"))
        (pcap:line bst ast)
        (pcap:line ast st)
(if (< xst (- xen (* da 2)))
(progn
  (setq col (abs (/ (- xst xen) (-(+ pcd da) (* da 1.414)) )))
  (setq xdd 0 ydd 0 ts 0 xdda 0.414)
  (while ( >= col 1 )
        (setq xa (+ xdd xst)
        ya (+ ydd yst)
        xb (+ da xdd xst)
        yb (-(+ ydd yst) da)
        xc (-(+ pcd da xdd xst)(* da 1.414))
        yc (-(+ ydd yst) da)
        aa (list xa ya )
        bb (list xb yb )
        cc (list xc yc ))
                (pcap:line aa bb)
                (pcap:line bb cc)
    (setq col (- col 1) ts (+ ts 1))
    (setq xdd (* xdda da ts -1) ydd (* ts da))
    (setq xdd (+ xdd (* pcd ts)))
    (setq ydd (* ydd -1))
  )
;last
                          (setq xa (+ xdd xst)
        ya (+ ydd yst)
        xb (+ da xdd xst)
        yb (-(+ ydd yst) da)
        xc (-(+ pcd da xdd xst)(* da 1.414))
        yc (-(+ ydd yst) da)
        aa (list xa ya )
        bb (list xb yb )
        cc (list xc yc ))
(if (< (* da 2.3) (abs (- xa xen)))
(progn
(pcap:line aa bb)
(pcap:line bb cc)
)
(pcap:line aa bb)
)
    (setq col (- col 1) ts (+ ts 1))
    (setq xdd (* xdda da ts -1) ydd (* ts da))
    (setq xdd (+ xdd (* pcd ts)))
    (setq ydd (* ydd -1))


)
)
(if (> xst (+ xen (* da 2)))
(progn
  (setq col (abs (/ (- xst xen) (-(+ pcd da) (* da 1.414)) )))
  (setq xdd 0 ydd 0 ts 0 xdda 0.414)
  (while ( >= col 1 )
        (setq xa (+ xdd xst)
        ya (+ ydd yst)
        xb (-(+ xdd xst) da)
        yb (-(+ ydd yst) da)
        xc (-(+ xdd xst (* da 1.414)) da pcd )
        yc (-(+ ydd yst) da)
        aa (list xa ya )
        bb (list xb yb )
        cc (list xc yc ))
                (pcap:line aa bb)
                (pcap:line bb cc)
    (setq col (- col 1) ts (+ ts 1))
    (setq xdd (* xdda da ts -1) ydd (* ts da))
    (setq xdd (* (+ xdd (* pcd ts)) -1))
    (setq ydd (* ydd -1))
  )
;last
                          (setq xa (+ xdd xst)
        ya (+ ydd yst)
        xb (-(+ xdd xst) da)
        yb (-(+ ydd yst) da)
        xc (-(+ xdd xst (* da 1.414)) da pcd )
        yc (-(+ ydd yst) da)
        aa (list xa ya )
        bb (list xb yb )
        cc (list xc yc ))
(if (< (* da 2.3) (abs (- xa xen)))
(progn
(pcap:line aa bb)
(pcap:line bb cc)
)
(pcap:line aa bb)
)
    (setq col (- col 1) ts (+ ts 1))
    (setq xdd (* xdda da ts -1) ydd (* ts da))
    (setq xdd (* (+ xdd (* pcd ts)) -1))
    (setq ydd (* ydd -1))

)
)


(if (< (* da 2.3) (abs (- xa xen)))
  (progn
  (VL-CMDF "_chamfer" "d" da da)
  (VL-CMDF "_chamfer" aa en)
  )
  (progn
  (VL-CMDF "_fillet" "r" 0)
  (VL-CMDF "_fillet" aa en)
  )
)
(setvar "OsnapCoord" 2)
)


(defun pcap:fanout-top ( da pcd st en turnst / nclayer xst yst xen yen xdd ydd ts xa ya xb yb xc yc aa bb cc row col)
(vl-load-com)
(setvar "OsnapCoord" 1)
  (setq xst (car st)
        yst (cadr st))
  (setq xen (car en)
        yen (cadr en))
  (setq nclayer (getvar "CLAYER"))

        (setq xst (- xst da)
        yst (+ yst da))
  (setq col (abs (/ (- xst xen) (-(+ pcd da) (* da 1.414)) )))
  (setq xdd 0 ydd 0 ts 0 xdda 0.414)
    (setq xa (+ xdd xst)
          ya (+ ydd yst)
          xb (+ da xdd xst)
          yb (-(+ ydd yst) da)
          xc (-(+ pcd da xdd xst)(* da 1.414))
          yc (-(+ ydd yst) da)
          aa (list xa ya )
          bb (list xb yb )
          cc (list xc yc ))
          (pcap:line bb cc)
                (setq cd010 bb)
      (setq col (- col 1) ts (+ ts 1))
    (setq xdd (* xdda da ts -1) ydd (* ts da))
    (setq xdd (+ xdd (* pcd ts)))
    (setq ydd (* ydd -1))

  (while ( > col 1 )
        (setq xa (+ xdd xst)
        ya (+ ydd yst)
        xb (+ da xdd xst)
        yb (-(+ ydd yst) da)
        xc (-(+ pcd da xdd xst)(* da 1.414))
        yc (-(+ ydd yst) da)
        aa (list xa ya )
        bb (list xb yb )
        cc (list xc yc ))
                (pcap:line aa bb)
                (pcap:line bb cc)
    (setq col (- col 1) ts (+ ts 1))
    (setq xdd (* xdda da ts -1) ydd (* ts da))
    (setq xdd (+ xdd (* pcd ts)))
    (setq ydd (* ydd -1))
  )
;last
                          (setq xa (+ xdd xst)
        ya (+ ydd yst)
        xb (+ da xdd xst)
        yb (-(+ ydd yst) da)
        xc (-(+ pcd da xdd xst)(* da 1.414))
        yc (-(+ ydd yst) da)
        aa (list xa ya )
        bb (list xb yb )
        cc (list xc yc ))
(if (< (* da 2.3) (abs (- xa xen)))
(progn
(pcap:line aa bb)
(pcap:line bb cc)
)
(pcap:line aa bb)
)
    (setq col (- col 1) ts (+ ts 1))
    (setq xdd (* xdda da ts -1) ydd (* ts da))
    (setq xdd (+ xdd (* pcd ts)))
    (setq ydd (* ydd -1))


(setq cd005x (car turnst)
      cd005y (cadr turnst))
(if ( > cd005x 0)
  (setq cd006x (- cd005x (- cd005y (cadr st) 0.2)))
  (setq cd006x (+ cd005x (- cd005y (cadr st) 0.2)))
)
(setq cd006y (- cd005y (- cd005y (cadr st) 0.2))
      cd005 (list cd005x cd005y )
      cd006 (list cd006x cd006y ))
(VL-CMDF "line" cd005 cd006 "")
(setq tp5 (cons cd006 tp5))

(setq cd010x (+ (car cd010) 3)
      cd010y (cadr cd010)
      cd010 (list cd010x cd010y ))
(setq tp6 (cons cd010 tp6))

(if (< (* da 2.3) (abs (- xa xen)))
  (progn
  (VL-CMDF "_chamfer" "d" da da)
  (VL-CMDF "_chamfer" aa en)
  )
  (progn
  (VL-CMDF "_fillet" "r" 0)
  (VL-CMDF "_fillet" aa en)
  )
)

(setvar "OsnapCoord" 2)
)

(defun pcap:fanout-vertical ( da pcd asw bsw ast en  / nclayer yast xast bst st yst xst yen xen ydd xdd ts ya xa yb xb yc xc aa bb cc row col)
(vl-load-com)
(setvar "OsnapCoord" 1)
  (setq xast (car ast)
        yast (cadr ast))
  (setq bst (list (+ xast bsw) yast))
  (setq st (list (- xast asw) yast))
  (setq xst (car st)
        yst (cadr st))
  (setq xen (car en)
        yen (cadr en))
  (setq nclayer (getvar "CLAYER"))
        (pcap:line bst ast)
        (pcap:line ast st)

  (setq col (abs (/ (- yst yen) (-(+ pcd da) (* da 1.414)) )))
  (setq ydd 0 xdd 0 ts 0 ydda 0.414)
  (while ( >= col 1 )
        (setq ya (+ ydd yst)
        xa (+ xdd xst)
        yb (-(+ ydd yst) da)
        xb (-(+ xdd xst) da)
        yc (-(+ ydd yst (* da 1.414)) da pcd )
        xc (-(+ xdd xst) da)
        aa (list xa ya)
        bb (list xb yb)
        cc (list xc yc))
                (pcap:line aa bb)
                (pcap:line bb cc)
    (setq col (- col 1) ts (+ ts 1))
    (setq ydd (* ydda da ts -1) xdd (* ts da))
    (setq ydd (* (+ ydd (* pcd ts)) -1))
    (setq xdd (* xdd -1))
  )
;last
                          (setq ya (+ ydd yst)
        xa (+ xdd xst)
        yb (-(+ ydd yst) da)
        xb (-(+ xdd xst) da)
        yc (-(+ ydd yst (* da 1.414)) da pcd )
        xc (-(+ xdd xst) da)
        aa (list xa ya )
        bb (list xb yb )
        cc (list xc yc ))
(if (< (* da 2.3) (abs (- ya yen)))
(progn
(pcap:line aa bb)
(pcap:line bb cc)
)
(pcap:line aa bb)
)
    (setq col (- col 1) ts (+ ts 1))
    (setq ydd (* ydda da ts -1) xdd (* ts da))
    (setq ydd (* (+ ydd (* pcd ts)) -1))
    (setq xdd (* xdd -1))

(setq pt5 (nth cdnum1 tp5))
(setq yb (- yb 0.3)
  bb (list xb yb ))
(setq cd038 bb)
(setq pt6 (nth cdnum1 tp6))
(VL-CMDF "_fillet" "r" 0)
(VL-CMDF "_fillet" cd038 pt5)
(VL-CMDF "_fillet" "r" 0)
(VL-CMDF "_fillet" pt5 pt6)
(setq cdnum1 (+ cdnum1 1))

(setvar "OsnapCoord" 2)
)


(defun pcap:generate(/ mrx mtx gap sgp tx rx xangle xbase1 ybase1 xbase2 ybase2 xa ya xb yb xc yc xd yd xaa yaa row col row1 col1 dt xe ye xf yf xg yg ee ff gg)
(vl-load-com)
(setvar "OsnapCoord" 1)

  (pcap:ensure-layer "Top ITO" 2)
        (pcap:ensure-layer "Top Ag" 3)
        (pcap:ensure-layer "Top laser" 1)
  (pcap:ensure-layer "Bottom ITO" 5)
  (pcap:ensure-layer "Bottom Ag" 190)
  (pcap:ensure-layer "Bottom laser" 211)

  (setq gap (pcap:getdist-default "\nSensor neck width" 1.0))
  (setq sgp (pcap:getdist-default "\nSensor electrode gap" 0.6))
  (setq tx  (pcap:getdist-default "\nSensor pitch TX" 5.0))
  (setq rx  (pcap:getdist-default "\nSensor pitch RX" 5.0))
  (setq col (pcap:getint-default  "\nSensor channels TX" 10))
  (setq row (pcap:getint-default  "\nSensor channels RX" 6))


        ;; The legacy file changed geometry according to CDATE.  That made the
        ;; same parameters produce different drawings on different days.
        ;; Preserve the normal legacy branch deterministically.
  (setq zmg 1)
  (setq mtx (* tx -0.5 (- col zmg)))
        (setq mrx (* rx -0.5 (- row zmg)))
  (setq ntx (* tx 0.5 (- col zmg)))
        (setq nrx (* rx 0.5 (- row zmg)))
        (setq dt 0.5 xaa mrx yaa mtx )

;;set bottom laser
  (setq da  (pcap:getdist-default "\nRX route spacing" 0.1))
        (setq da2 (pcap:getdist-default "\nFPC pin pitch" 0.8))



;;rx pin laser
  (setq lmp1 (getpoint "\n RX的中心點"))


(if (=  (rem row 2) 0)
(progn
  (setq xlmp (car lmp1)
        xlmp (+ xlmp (* (+ (/ row 2) 2) da2 )))
)
)
(if (> (rem row 2) 0)
(progn
  (setq xlmp (car lmp1)
              xlmp (+ xlmp (* (+ (/ row 2) 2.5 ) da2 )))
)
)
(setq tp1 nil)
(setq lmp3 (+ row 3)
      ylmp mtx
      ylmp2 (- ylmp 20))

(repeat lmp3
  (setq xlmp (- xlmp da2 )
              lmp1 (list xlmp ylmp )
        lmp2 (list xlmp ylmp2 ))
        (setq tp1 (cons lmp2 tp1))
        (VL-CMDF "layer" "s" "Bottom laser" "")
        (VL-CMDF "_line" lmp1 lmp2 "")
)
  (setq num lmp3)
  (setq pt1 (nth 0 tp1))
  (setq cd101 (list (car pt1) (car (cdr pt1))))
  (setq pt1 (nth (- num 1)tp1))
  (setq cd102 (list (car pt1) (car (cdr pt1))))





;;tx pin laser
  (setq lmp1 (getpoint "\n TX的中心點"))
(if (=  (rem col 2) 0)
(progn
  (setq xlmp (car lmp1)
        xlmp (+ xlmp (* (+ (/ col 2) 2) da2 )))
)
)

(if (> (rem col 2) 0)
(progn
  (setq xlmp (car lmp1)
              xlmp (+ xlmp (* (+ (/ col 2) 2.5 ) da2 )))
)
)

(setq tp2 nil)
(setq lmp3 (+ col 3)
      ylmp mtx
      ylmp2 (- ylmp 20))

(repeat lmp3
  (setq xlmp (- xlmp da2 )
              lmp1 (list xlmp ylmp )
        lmp2 (list xlmp ylmp2 ))
        (setq tp2 (cons lmp2 tp2))
        (VL-CMDF "layer" "s" "Top laser" "")
        (VL-CMDF "_line" lmp1 lmp2 "")
)
  (setq num2 lmp3)

(getpoint "\n 請將鎖點關閉，在圖面點任意點開始繪圖")

;;Lbottom ito right
  (VL-CMDF "layer" "s" "Bottom ITO" "")
  (setq xangle (atan (/ tx rx)))
  (setq xbase1 (- (/ rx 2) (/ sgp (* 2 (sin xangle))))
        ybase1 (/ tx 2)
        xbase2 (/ gap 2)
        ybase2 (- (/ tx 2) ( * (/ (sin xangle)(cos xangle)) (-(-(/ rx 2)(/ sgp (* 2 (sin xangle))))(/ gap 2))))
  )

  (setq row1 row col1 col)
  (while ( > row1 0 )

      (setq xe xaa)
    (setq ye (+ yaa (* -1 (+ dt (/ tx 2)))))
    (setq xf (+ xaa (* xbase1 1)))
    (setq yf ye)
    (setq xg (+ xaa (* xbase1 zmg)))
    (setq yg (+ yaa (* ybase1 -1)))
    (setq ee (list xe ye )
          ff (list xf yf )
          gg (list xg yg )
    )
                (pcap:line ee ff)
                (pcap:line ff gg)
;Ibottom ag
    (VL-CMDF "layer" "s" "Bottom Ag" "")
    (setq hhx (nth 0 ee))
    (setq hhy (nth 1 gg))
    (setq hh (list hhx hhy))
    (setq iix (+ xaa (/ rx 2)))
    (setq iiy (nth 1 ff))
    (setq ii (list iix iiy))
                (pcap:line ii ff)
                (pcap:line ff gg)
                (pcap:line gg hh)
;

    (VL-CMDF "layer" "s" "Bottom ITO" "")

    (setq col1 col)
    (while ( > col1 0 )
    (setq xa (+ xaa(* xbase1 1))
                ya (+ yaa(* ybase1 1))
          xb (+ xaa(* xbase2 1))
              yb (+ yaa(* ybase2 1))
                xc (+ xaa(* xbase2 1))
                yc (+ yaa(* ybase2 -1))
                xd (+ xaa(* xbase1 1))
                yd (+ yaa(* ybase1 -1))
          )
    (setq aa (list xa ya )
          bb (list xb yb )
          cc (list xc yc )
          dd (list xd yd )
    )
                (pcap:line aa bb)
                (pcap:line bb cc)
                (pcap:line cc dd)

    (setq col1 (- col1 1) yaa (+ yaa tx))
    )

      (setq yaa (- yaa tx))
    (setq xe xaa)
    (setq ye (+ yaa(+ dt (/ tx 2))))
    (setq xf (+ xaa(* xbase1 zmg)))
    (setq yf ye)
    (setq xg (+ xaa(* xbase1 zmg)))
    (setq yg (+ yaa(* ybase1 zmg)))
    (setq ee (list xe ye )
          ff (list xf yf )
          gg (list xg yg )
    )
                (pcap:line ee ff)
                (pcap:line ff gg)
;Nbottom ag
    (VL-CMDF "layer" "s" "Bottom Ag" "")
    (setq hhx (nth 0 ee))
    (setq hhy (nth 1 gg))
    (setq hh (list hhx hhy))
                (pcap:line ee ff)
                (pcap:line ff gg)
                (pcap:line gg hh)
;
    (VL-CMDF "layer" "s" "Bottom ITO" "")
    (setq yaa mtx)
    (setq row1 (- row1 1) xaa (+ xaa rx))
  )
  (setq xaa mrx yaa mtx)
;
;;Ybottom ito lift
  (setq row1 row col1 col)
  (while ( > row1 0 )

    (setq xe xaa)
    (setq ye (+ yaa (* -1 (+ dt (/ tx 2)))))
    (setq xf (+ xaa (* xbase1 -1)))
    (setq yf ye)
    (setq xg (+ xaa (* xbase1 -1)))
    (setq yg (+ yaa (* ybase1 -1)))
    (setq ee (list xe ye )
          ff (list xf yf )
          gg (list xg yg )
    )
                (pcap:line ee ff)
                (pcap:line ff gg)
;Ubottom ag
    (VL-CMDF "layer" "s" "Bottom Ag" "")
    (setq hhx (nth 0 ee))
    (setq hhy (nth 1 gg))
    (setq hh (list hhx hhy))
    (setq iix (- xaa (/ rx 2)))
    (setq iiy (nth 1 ff))
    (setq ii (list iix iiy))
                (pcap:line ii ff)
                (pcap:line ff gg)
                (pcap:line gg hh)
;

    (VL-CMDF "layer" "s" "Bottom ITO" "")
    (setq col1 col)
    (while ( > col1 0 )
    (setq xa (+ xaa(* xbase1 -1))
                ya (+ yaa(* ybase1 1))
          xb (+ xaa(* xbase2 -1))
              yb (+ yaa(* ybase2 1))
                xc (+ xaa(* xbase2 -1))
                yc (+ yaa(* ybase2 -1))
                xd (+ xaa(* xbase1 -1))
                yd (+ yaa(* ybase1 -1))
          )
    (setq aa (list xa ya )
          bb (list xb yb )
          cc (list xc yc )
          dd (list xd yd )
    )
                (pcap:line aa bb)
                (pcap:line bb cc)
                (pcap:line cc dd)

    (setq col1 (- col1 1) yaa (+ yaa tx))
    )

      (setq yaa (- yaa tx))
    (setq xe xaa)
    (setq ye (+ yaa(+ dt (/ tx 2))))
    (setq xf (+ xaa(* xbase1 -1)))
    (setq yf ye)
    (setq xg (+ xaa(* xbase1 -1)))
    (setq yg (+ yaa(* ybase1 1)))
    (setq ee (list xe ye )
          ff (list xf yf )
          gg (list xg yg )
    )
                (pcap:line ee ff)
                (pcap:line ff gg)
;Ybottom ag
    (VL-CMDF "layer" "s" "Bottom Ag" "")
    (setq hhx (nth 0 ee))
    (setq hhy (nth 1 gg))
    (setq hh (list hhx hhy))
    (VL-CMDF "line" ee ff gg hh "")
;
    (VL-CMDF "layer" "s" "Bottom ITO" "")
    (setq yaa mtx)
    (setq row1 (- row1 1) xaa (+ xaa rx))
  )
  (setq xaa mrx yaa mtx)



;;Utop ito up
  (VL-CMDF "layer" "s" "Top ITO" "")
  (setq xangle (atan (/ tx rx)))
  (setq xbase1 (/ rx 2)
        ybase1 (- (/ tx 2) (/ sgp (* 2 (cos xangle))))
        xbase2 (- (/ rx 2) ( * (/(cos xangle)(sin xangle)) (-(-(/ tx 2)(/ sgp (* 2 (cos xangle))))(/ gap 2))))
        ybase2 (/ gap 2)
  )
  (setq row1 row col1 col)
  (while ( > col1 0 )

      (setq xe (+ xaa (* -1 (+ dt (/ rx 2)))))
    (setq ye yaa)
    (setq xf xe)
    (setq yf (+ yaa (* ybase1 1)))
    (setq xg (+ xaa (* xbase1 -1)))
    (setq yg (+ yaa (* ybase1 1)))
    (setq ee (list xe ye )
          ff (list xf yf )
          gg (list xg yg )
    )
                (pcap:line ee ff)
                (pcap:line ff gg)
;top ag
    (VL-CMDF "layer" "s" "Top Ag" "")
    (setq hhx (nth 0 gg))
    (setq hhy (nth 1 ee))
    (setq hh (list hhx hhy))
    (setq iix (nth 0 ff))
    (setq iiy (+ yaa (/ tx 2)))
    (setq ii (list iix iiy))
                (pcap:line ii ff)
                (pcap:line ff gg)
                (pcap:line gg hh)
;
    (VL-CMDF "layer" "s" "Top ITO" "")
    (setq row1 row)
    (while ( > row1 0 )
    (setq xa (+ xaa(* xbase1 1))
                ya (+ yaa(* ybase1 1))
          xb (+ xaa(* xbase2 1))
              yb (+ yaa(* ybase2 1))
                xc (+ xaa(* xbase2 -1))
                yc (+ yaa(* ybase2 1))
                xd (+ xaa(* xbase1 -1))
                yd (+ yaa(* ybase1 1))
          )
    (setq aa (list xa ya )
          bb (list xb yb )
          cc (list xc yc )
          dd (list xd yd )
    )
                (pcap:line aa bb)
                (pcap:line bb cc)
                (pcap:line cc dd)

    (setq row1 (- row1 1) xaa (+ xaa rx))
    )
    (setq xaa (- xaa rx))
      (setq xe (+ xaa (* 1 (+ dt (/ rx 2)))))
    (setq ye yaa)
    (setq xf xe)
    (setq yf (+ yaa (* ybase1 1)))
    (setq xg (+ xaa (* xbase1 1)))
    (setq yg (+ yaa (* ybase1 1)))
    (setq ee (list xe ye )
          ff (list xf yf )
          gg (list xg yg )
    )
                (pcap:line ee ff)
                (pcap:line ff gg)
;top ag
    (VL-CMDF "layer" "s" "Top Ag" "")
    (setq hhx (nth 0 gg))
    (setq hhy (nth 1 ee))
    (setq hh (list hhx hhy))
    (setq iix (nth 0 ff))
    (setq iiy (+ yaa (/ tx 2)))
    (setq ii (list iix iiy))
                (pcap:line ii ff)
                (pcap:line ff gg)
                (pcap:line gg hh)
;
    (VL-CMDF "layer" "s" "Top ITO" "")

    (setq xaa mrx)
    (setq col1 (- col1 1) yaa (+ yaa tx))
  )
  (setq xaa mrx yaa mtx)
;
;;top ito down
  (setq row1 row col1 col)
  (while ( > col1 0 )

      (setq xe (+ xaa (* -1 (+ dt (/ rx 2)))))
    (setq ye yaa)
    (setq xf xe)
    (setq yf (+ yaa (* ybase1 -1)))
    (setq xg (+ xaa (* xbase1 -1)))
    (setq yg (+ yaa (* ybase1 -1)))
    (setq ee (list xe ye )
          ff (list xf yf )
          gg (list xg yg )
    )
                (pcap:line ee ff)
                (pcap:line ff gg)
;top ag
    (VL-CMDF "layer" "s" "Top Ag" "")
    (setq hhx (nth 0 gg))
    (setq hhy (nth 1 ee))
    (setq hh (list hhx hhy))
    (setq iix (nth 0 ff))
    (setq iiy (- yaa (/ tx 2)))
    (setq ii (list iix iiy))
                (pcap:line ii ff)
                (pcap:line ff gg)
                (pcap:line gg hh)
;
    (VL-CMDF "layer" "s" "Top ITO" "")
    (setq row1 row)
    (while ( > row1 0 )
    (setq xa (+ xaa(* xbase1 1))
                ya (+ yaa(* ybase1 -1))
          xb (+ xaa(* xbase2 1))
              yb (+ yaa(* ybase2 -1))
                xc (+ xaa(* xbase2 -1))
                yc (+ yaa(* ybase2 -1))
                xd (+ xaa(* xbase1 -1))
                yd (+ yaa(* ybase1 -1))
          )
    (setq aa (list xa ya )
          bb (list xb yb )
          cc (list xc yc )
          dd (list xd yd )
    )
                (pcap:line aa bb)
                (pcap:line bb cc)
                (pcap:line cc dd)

    (setq row1 (- row1 1) xaa (+ xaa rx))
    )
    (setq xaa (- xaa rx))
      (setq xe (+ xaa (* 1 (+ dt (/ rx 2)))))
    (setq ye yaa)
    (setq xf xe)
    (setq yf (+ yaa (* ybase1 -1)))
    (setq xg (+ xaa (* xbase1 1)))
    (setq yg (+ yaa (* ybase1 -1)))
    (setq ee (list xe ye )
          ff (list xf yf )
          gg (list xg yg )
    )
                (pcap:line ee ff)
                (pcap:line ff gg)
;top ag
    (VL-CMDF "layer" "s" "Top Ag" "")
    (setq hhx (nth 0 gg))
    (setq hhy (nth 1 ee))
    (setq hh (list hhx hhy))
    (setq iix (nth 0 ff))
    (setq iiy (- yaa (/ tx 2)))
    (setq ii (list iix iiy))
                (pcap:line ii ff)
                (pcap:line ff gg)
                (pcap:line gg hh)
;
    (VL-CMDF "layer" "s" "Top ITO" "")

    (setq xaa mrx)
    (setq col1 (- col1 1) yaa (+ yaa tx))
  )
  (setq xaa mrx yaa mtx)
;bottom ag outsile

(setq cd001x (- xaa(/ rx 2)))
(setq cd001y (- yaa dt (/ tx 2)))
(setq cd002x (- cd001x (* da 0.828)))
(setq cd002y cd001y)
(setq cd001 (list cd001x cd001y )
      cd002 (list cd002x cd002y )
)
(setq cd003x (* cd001x -1))
(setq cd003y cd001y)
(setq cd004x (* cd002x -1))
(setq cd004y cd001y)
(setq cd003 (list cd003x cd003y )
      cd004 (list cd004x cd004y )
)

(VL-CMDF "layer" "s" "Bottom Ag" "")
(VL-CMDF "line" cd001 cd002 "")
(VL-CMDF "line" cd003 cd004 "")

(setq azoomx (+ (car cd101) 20)
      azoomy (+ (cadr cd001) 8)
      bzoomx (+ (car cd102) -20)
      bzoomy (+ (cadr cd001) -35)
      azoom1 (list azoomx azoomy )
      bzoom1 (list bzoomx bzoomy )
)
(pcap:fanout-horizontal da rx 0.3 0 cd002 cd101 )
(pcap:fanout-horizontal da rx 0.3 0 cd004 cd102 )
(VL-CMDF "layer" "s" "Bottom laser" "")

;bottom laser
(setq cd201 cd001)
(setq cd201x (car cd201))
(setq pt1 (nth 1 tp1))
(setq cd202 (list (car pt1) (car (cdr pt1))))
(pcap:fanout-horizontal da rx 0.1 0.5 cd201 cd202 )
(setq num (- num 3))
(setq x 1)

(repeat num
(setq pt1 (nth (+ x zmg) tp1))
(setq cd201x (+ cd201x rx))
(setq cd201 (list cd201x cd001y))
(setq cd202 (list (car pt1) (car (cdr pt1))))

(if (> (abs(-(car pt1) cd201x)) 0.3)
(pcap:fanout-horizontal da rx 0.1 0.5 cd201 cd202 )
)

(setq x (+ x zmg))
)

;;;;;;;;;;;;;;;;;;;;;;;;;;top
(setq pt3 (nth (- num2 1)tp2))
(setq cd103 (list (car pt3) (car (cdr pt3))))
(setq cd103x (car cd103))
(setq cd501 (/ (abs(- cd002x cd103x )) 100))
(if (< cd501 0.5)
    (setq cd501 0.5))

(setq cd020x (- cd002x 0.3)
      cd020y (- cd002y cd501 0.3)
      cd020 (list cd020x cd020y ))
(setq cd030x (- cd002x -0.1 (* 0.414 cd501))
      cd030y (- cd002y 0.3 0.1 cd501)
      cd030 (list cd030x cd030y ))
(setq pt3 (nth (- num2 1)tp2))
(setq cd040 (list (car pt3) (car (cdr pt3))))
(VL-CMDF "layer" "s" "Top Ag" "")
(setq azoomx (+ (car cd040) -65)
      azoomy (+ (cadr cd030) 8)
      bzoomx (+ (car cd040) 5)
      bzoomy (+ (cadr cd030) -25)
      azoom1 (list azoomx azoomy )
      bzoom1 (list bzoomx bzoomy )
)

(setq tp5 nil)
(setq tp6 nil)
(pcap:fanout-top da rx cd030 cd040 cd020)
(setq cd021x (- cd020x (* 1.41421 0.2))
      cd021y cd020y
      cd021 (list cd021x cd021y ))
(setq cd031x (- cd030x (* 0.414 0.2))
      cd031y (- cd030y  (* da 2) )
      cd031 (list cd031x cd031y ))
(setq pt3 (nth (- num2 2)tp2))
(setq cd040 (list (car pt3) (car (cdr pt3))))
(VL-CMDF "layer" "s" "Top laser" "")
(pcap:fanout-top da rx cd031 cd040 cd021)
(setq cdnum1 2)
(repeat col
(setq cdnum1 (+ cdnum1 1))
(setq cd022x (- cd021x (* 1.41421 0.1))
      cd022y cd021y
      cd022 (list cd022x cd022y ))
(setq cd032x (- cd031x (* 0.414 0.1))
      cd032y (- cd031y  da )
      cd032 (list cd032x cd032y ))
(setq pt3 (nth (- num2 cdnum1)tp2))
(setq cd040 (list (car pt3) (car (cdr pt3))))
(pcap:fanout-top da rx cd032 cd040 cd022)
(setq cd021x cd022x)
(setq cd031x cd032x)
(setq cd031y cd032y)
)
(setq cdnum1 (+ cdnum1 zmg))
(setq cd022x (- cd021x (* 1.41421 0.2))
      cd022y cd021y
      cd022 (list cd022x cd022y ))
(setq cd032x (- cd031x (* 0.414 0.2))
      cd032y (- cd031y  (* da 2) )
      cd032 (list cd032x cd032y ))

(setq pt3 (nth (- num2 cdnum1)tp2))
(setq cd040 (list (car pt3) (car (cdr pt3))))
(VL-CMDF "layer" "s" "Top Ag" "")
(pcap:fanout-top da rx cd032 cd040 cd022)



(setq cd037x (- (* rx row -0.5) 0.5)
      cd037y (* tx col -0.5)
      cd037 (list cd037x cd037y ))

(setq azoomx (+ (car cd037) -10)
      azoomy (+ (cadr cd037) 10)
      bzoomx (+ (car cd037) 10)
      bzoomy (+ (cadr cd037) -10)
      azoom1 (list azoomx azoomy )
      bzoom1 (list bzoomx bzoomy )
)
(setq num3 (length tp5))
(setq pt5 (nth (- num3 1) tp5))
(setq pt6 (nth (- num3 1) tp6))
(VL-CMDF "fillet" "r" 0)
(VL-CMDF "fillet" cd037 pt5)
(VL-CMDF "fillet" "r" 0)
(VL-CMDF "fillet" pt5 pt6)


(setq cd035x (- (* rx row -0.5) 0.5)
      cd035y (* tx col 0.5)
      cd035 (list cd035x cd035y ))
(setq cd036x (- (* rx row -0.5) 0.5)
      cd036y (+ (* tx col 0.5) (* da 0.828))
      cd036 (list cd036x cd036y ))
(VL-CMDF "line" cd035 cd036 "")
(setq cdnum1 0)
(pcap:fanout-vertical 0.1 tx 0.3 0 cd036 cd021 )

(VL-CMDF "layer" "s" "Top laser" "")
(pcap:fanout-vertical 0.1 tx 0.1 0.5 cd035 cd021 )
(repeat col
(setq cd035y (- cd035y tx)
      cd035 (list cd035x cd035y ))
(pcap:fanout-vertical 0.1 tx 0.1 0.5 cd035 cd021 )
)

(setvar "OsnapCoord" 2)
)

(defun c:PCAPSENSOR
  (/ *error* old-cmdecho old-osnapcoord undo-open)
  (setq old-cmdecho   (getvar "CMDECHO")
        old-osnapcoord (getvar "OSNAPCOORD")
        undo-open nil)

  (defun *error* (message)
    (if undo-open (command-s "_.UNDO" "_End"))
    (setvar "CMDECHO" old-cmdecho)
    (setvar "OSNAPCOORD" old-osnapcoord)
    (if (and message
             (not (wcmatch (strcase message) "*BREAK*,*CANCEL*,*EXIT*")))
      (prompt (strcat "\nPCAPSENSOR error: " message)))
    (princ))

  (setvar "CMDECHO" 0)
  (command-s "_.UNDO" "_Begin")
  (setq undo-open T)
  (pcap:generate)
  (command-s "_.UNDO" "_End")
  (setq undo-open nil)
  (setvar "CMDECHO" old-cmdecho)
  (setvar "OSNAPCOORD" old-osnapcoord)
  (prompt "\nPCAPSENSOR completed.")
  (princ))

(prompt "\nPCAP Sensor Layout Generator loaded. Run PCAPSENSOR.")
(princ)
